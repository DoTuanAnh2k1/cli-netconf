module ne-system {
  namespace "urn:params:xml:ns:yang:ne-system";
  prefix sys;

  organization "5GC Team";
  contact "5GC Team";
  description
    "YANG module for 5GC Network Element system configuration.
     Used with ConfD for NETCONF-based management.";

  revision 2024-01-01 {
    description "Initial revision.";
  }

  // ---------------------------------------------------------------------------
  // Reusable groupings
  // ---------------------------------------------------------------------------

  grouping ntp-server-config {
    description "NTP server entry fields.";

    leaf address {
      type string;
      description "NTP server address (IP or hostname).";
    }

    leaf prefer {
      type boolean;
      default false;
      description "Prefer this NTP server.";
    }
  }

  grouping ipv4-config {
    description "IPv4 address configuration.";

    leaf address {
      type string;
      description "IPv4 address in dotted notation.";
    }

    leaf prefix-length {
      type uint8 {
        range "0..32";
      }
      description "Subnet prefix length.";
    }

    leaf gateway {
      type string;
      description "Default gateway.";
    }
  }

  // ---------------------------------------------------------------------------
  // Top-level containers
  // ---------------------------------------------------------------------------

  container system {
    description "Top-level system configuration.";

    leaf hostname {
      type string {
        length "1..255";
      }
      description "The hostname of the network element.";
    }

    leaf location {
      type string;
      description "Physical location of the NE.";
    }

    leaf contact {
      type string;
      description "Administrative contact information.";
    }

    container ntp {
      description "NTP configuration.";

      leaf enabled {
        type boolean;
        default true;
        description "Enable or disable NTP.";
      }

      list server {
        key "address";
        description "NTP server list.";
        uses ntp-server-config;
      }
    }

    container dns {
      description "DNS resolver configuration.";

      leaf-list search {
        type string;
        description "DNS search domain list.";
      }

      list server {
        key "address";
        ordered-by user;
        description "DNS server list.";

        leaf address {
          type string;
          description "DNS server IP address.";
        }
      }
    }

    container logging {
      description "System logging configuration.";

      leaf level {
        type enumeration {
          enum emergency;
          enum alert;
          enum critical;
          enum error;
          enum warning;
          enum notice;
          enum info;
          enum debug;
        }
        default info;
        description "Global log level.";
      }

      list remote-server {
        key "address";
        description "Remote syslog servers.";

        leaf address {
          type string;
          description "Syslog server address.";
        }

        leaf port {
          type uint16;
          default 514;
          description "Syslog server port.";
        }

        leaf protocol {
          type enumeration {
            enum udp;
            enum tcp;
          }
          default udp;
        }
      }
    }
  }

  container interfaces {
    description "Network interface configuration.";

    list interface {
      key "name";
      description "Interface list.";

      leaf name {
        type string;
        description "Interface name.";
      }

      leaf description {
        type string;
        description "Interface description.";
      }

      leaf enabled {
        type boolean;
        default true;
        description "Enable or disable this interface.";
      }

      leaf mtu {
        type uint16 {
          range "68..9000";
        }
        default 1500;
        description "Maximum transmission unit.";
      }

      container ipv4 {
        description "IPv4 configuration.";
        uses ipv4-config;
      }
    }
  }
}
